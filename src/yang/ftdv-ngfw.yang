module ftdv-ngfw {

  namespace "http://example.com/ftdv-ngfw";
  prefix ftdv-ngfw;

  import ietf-inet-types { prefix inet; }
  import tailf-common { prefix tailf; }
  import tailf-ncs { prefix ncs; }
  import tailf-etsi-rel2-nfvo { prefix nfvo-rel2; }

  description
    "VNF deployment service for VMWare using Cisco NFVO package";

  revision 2019-03-12 {
    description
      "Initial revision.";
  }
  identity vnfs-configured {
    base ncs:plan-state;
  }

  identity vnfs-deployed {
    base ncs:plan-state;
  }
  identity vnfs-api-available {
    base ncs:plan-state;
  }
  identity monitoring-disabled {
    base ncs:plan-state;
  }
  identity vnfs-registered-with-nso {
    base ncs:plan-state;
  }
  identity vnfs-initialized {
    base ncs:plan-state;
  }
  identity scaling-monitoring-enabled {
    base ncs:plan-state;
  }
  identity vnfs-users-created {
    base ncs:plan-state;
  }
  identity vnfs-synchronized-with-nso {
    base ncs:plan-state;
  }
  identity itd-configured {
    base ncs:plan-state;
  }

  identity vnf {
    base ncs:plan-component-type;
  }
  identity registered-with-nso {
    base ncs:plan-state;
  }
  identity initialized {
    base ncs:plan-state;
  }
  identity users-created {
    base ncs:plan-state;
  }
  identity syncronized-with-nso {
    base ncs:plan-state;
  }

  grouping access-rule-grouping {
    list access-rule {
      key name;
      leaf name {
        type string;
      }
      leaf source-zone {
        type string;
//        tailf:non-strict-leafref {
//          path "../../state/zone/name";
//        }
      }
      leaf source-port {
        type string;
//        tailf:non-strict-leafref {
//          path "../../state/port/name";
//        }
      }
      leaf action {
        type enumeration {
          enum "PERMIT";
          enum "TRUST";
          enum "DENY";
        }
      }
    }
  }

  grouping state-grouping {
    container state {
      config "false";
      list zone {
        key name;
        leaf name {
          type string;
        }
        leaf id {
          type string;
        }
      }
      list port {
        key name;
        leaf name {
          type string;
        }
        leaf id {
          type string;
        }
      }
      list user {
        key name;
        leaf name {
          type string;
        }
        leaf id {
          type string;
        }
      }
    }
  }

  grouping action-grouping {
    tailf:action get-device-data {
      tailf:actionpoint ftdv-ngfw-getDeviceData-action;
      input {
      }
      output {
        leaf result {
          type string;
        }
      }
    }
    tailf:action add-user {
      tailf:actionpoint ftdv-ngfw-addUser-action;
      input {
        leaf username {
          mandatory "true";
          type string;
        }
        leaf password {
          mandatory "true";
          type string;
        }
      }
      output {
        leaf result {
          type string;
        }
      }
    }
    tailf:action delete-user {
      tailf:actionpoint ftdv-ngfw-deleteUser-action;
      input {
        leaf username {
          tailf:info "Name of user to delete (if no user available run get-device-data action)";
          mandatory "true";
          type leafref {
            path "../../state/user/name";
          }
        }
      }
      output {
        leaf result {
          type string;
        }
      }
    }
  }

  grouping vnf-deployment-grouping {
    leaf deployment-name {
      tailf:info "Unique deployment/service id";
      tailf:cli-allow-range;
      type string;
    }

    leaf tenant {
      tailf:info "Tenant of this site and owner of the VNF";
      type leafref {
        path "/ftdv-ngfw:vnf-manager/ftdv-ngfw:site/ftdv-ngfw:tenant";
      }
    }

    leaf catalog-vnf {
      tailf:info "VNF from the catalog to deploy";
      type leafref {
        path "/ftdv-ngfw:vnf-manager/ftdv-ngfw:vnf-catalog/ftdv-ngfw:name";
      }
    }

    container scaling {
/*
      tailf:info "Scaling attributes for the VNF";
      leaf minimum {
        tailf:info "Minumum number of VNFs to deploy";
        type uint8;
        must "current() > 0";
      }
      leaf maximum {
        tailf:info "Minumum number of VNFs to deploy";
        type uint8;
        must "current() >= ../minimum";
      }
*/
      leaf scale-up-threshold {
        tailf:info "Threshold to signal addition VNFs are needed";
        type uint8;
        must "current() > 0";
      }
      leaf scale-down-threshold {
        tailf:info "Threshold to signal that VNFs can be decommissioned";
        type uint8;
        must "current() > 0";
      }
      leaf ip-pool-start-address {
        tailf:info "IP address pool start address";
        type inet:ipv4-address;
        mandatory "true";
      }
      leaf ip-pool-end-address {
        tailf:info "IP address pool start address";
        type inet:ipv4-address;
        mandatory "true";
      }
    }

    leaf status {
      tailf:info "Status of the Deployment (inclusive of all VNFs)";
      config "false";
      type enumeration {
        enum "Unknown";
        enum "Deploying";
        enum "Starting VNFs";
        enum "Provisioning";
        enum "Configurable";
        enum "Failure";
      }
      default "Unknown";
    }

    list device {
      tailf:info "Information about devices in the Deployment";
      config "false";
      key name;
      leaf name {
        type string;
      }
      leaf management-ip-address {
        type string;
      }
      uses action-grouping;
      uses state-grouping;
    }

  }

  container vnf-manager {
    list site {
      tailf:info "VNF Deployment Site";
      key name;
      leaf name {
        tailf:info "Name of the Site";
        type string;
      }
      leaf-list tenant {
        tailf:info "Tenant of the site";
        type string;
      }
      leaf datacenter-name {
        tailf:info "VMWare datacenter name";
        type string;
        mandatory "true";
      }
      leaf cluster-name {
        tailf:info "VMWare compute cluster name";
        type string;
        mandatory "true";
      }
      leaf datastore-name {
        tailf:info "VMWare datastore name";
        type string;
        mandatory "true";
      }
      leaf dns-ip-address {
        tailf:info "DNS server IP address";
        type inet:ipv4-address;
        mandatory "true";
      }
      container management-network {
        tailf:info "Site's management network configuration";
        leaf name {
          tailf:info "VMware network name";
          type string;
          mandatory "true";
        }
        leaf netmask {
          tailf:info "Netmask (ie. 255.255.255.0)";
          type inet:ipv4-address;
          mandatory "true";
        }
        leaf gateway-ip-address {
          tailf:info "Gateway IP address";
          type inet:ipv4-address;
          mandatory "true";
        }
        leaf ip-address-resource-pool {
          tailf:info "Resource Pool for IP addresses";
          type string;
          mandatory "true";
        }
      }
      leaf elastic-services-controller {
        tailf:info "ESC devices that manages this site";
        type leafref {
          path "/ncs:devices/ncs:device/ncs:name";
        }
  //      must "deref(.)/../module[name='esc']" {
  //      must "deref(.)/../module/name ='esc'" {
  //        tailf:dependency "/ncs:devices/ncs:device/ncs:name";
  //      }
        mandatory "true";
      }
      list vnf-deployment {
        description "Service to stand up scalable FTDv using NFVO Service Pack";
        tailf:info "Service to stand up scalable FTDv using NFVO Service Pack";

        uses ncs:plan-data;
        uses ncs:service-progress-monitoring-data;
        uses ncs:service-data;
        ncs:servicepoint ftdv-ngfw-scalable-servicepoint;

        key "tenant deployment-name";
        uses vnf-deployment-grouping;
      }
    }

    list vnf-catalog {
      key name;
      leaf name {
        tailf:info "Name of the VNF";
        type string;
      }
      leaf descriptor-name {
        tailf:info "Name of the VNFD from nfvo/vnfd";
        type leafref {
          path "/nfvo-rel2:nfvo/nfvo-rel2:vnfd/nfvo-rel2:id";
        }
        mandatory "true";
      }
      leaf descriptor-flavor {
        tailf:info "Name of the VNFD flavor";
        type leafref {
          path "deref(../ftdv-ngfw:descriptor-name)/../nfvo-rel2:deployment-flavor/nfvo-rel2:id";
        }
        when "../descriptor-name";
        mandatory "true";
      }
      leaf descriptor-instantiation-level {
        tailf:info "Name of the VNFD instantiation level";
        type leafref {
          path "deref(../ftdv-ngfw:descriptor-flavor)/../nfvo-rel2:instantiation-level/nfvo-rel2:id";
        }
        when "../descriptor-flavor";
        mandatory "true";
      }
      leaf descriptor-vdu {
        tailf:info "Name of the VNFD virtualisation deployment unit";
        type leafref {
          path "deref(../ftdv-ngfw:descriptor-instantiation-level)/../nfvo-rel2:vdu-level/nfvo-rel2:vdu";
        }
        when "../descriptor-instantiation-level";
        mandatory "true";
      }
      leaf bootup-time {
        tailf:info "Maximum time to wait for VNF to be available";
        type uint32;
        mandatory "true";
      }
      leaf recovery-time {
        tailf:info "Maximum time to wait for VNF to restart";
        type uint32;
        mandatory "true";
      }
      leaf authgroup {
        tailf:info "NSO authgroup to use to connect to the VNF";
        type leafref {
          path "/ncs:devices/ncs:authgroups/ncs:group/ncs:name";
        }
        mandatory "true";
      }
      leaf esc-device-template {
        tailf:info "ESC template";
        type leafref {
          path "/ncs:devices/ncs:template/ncs:name";
        }
      }
    }
  }

  container firewall {
    list ftdv-ngfw-advanced {
      description "Service to stand up a FTDv with automated scaling and load balancing";

      key "site tenant deployment-name";
      leaf site {
        type leafref {
          path "/ftdv-ngfw:vnf-manager/ftdv-ngfw:site/ftdv-ngfw:name";
        }
      }
      uses ncs:plan-data;
      uses ncs:service-progress-monitoring-data;
      uses ncs:service-data;
      ncs:servicepoint ftdv-ngfw-advanced-servicepoint;

      uses vnf-deployment-grouping;
      uses access-rule-grouping;
    }

    list ftdv-ngfw-basic {
      description "Service to stand up a single FTDv using ESC directly";

      key deployment-name;
      leaf deployment-name {
        tailf:info "Unique deployment/service id";
        tailf:cli-allow-range;
        type string;
      }

      uses ncs:service-data;
      ncs:servicepoint ftdv-ngfw-servicepoint;

      leaf ip-address {
        type inet:ipv4-address;
      }

      uses action-grouping;
      uses state-grouping;
      uses access-rule-grouping;
    }
  }

  grouping itd-side {
      leaf device-ip-address;
      leaf from-interface;
  }
  grouping itd-ifra {
      list switches
  }

  list intelligent-traffic-director {
    key name;
    leaf name {
      type string;
    }
    uses ncs:service-data;
    ncs:servicepoint ftdv-itd-servicepoint;

    container infra {
      uses itd-ifra
    }
    container side-a {
      uses itd-side
    }
    container side-a {
      uses itd-side
    }
  }
}
